'Name:Creating a New Document from a Seed Model
'Version: 
'Code:CATIA CATScript
'Purpose: 从模型建立文档
'Author:gaochaofeng  
'Date:26.03.2022
'Change:

Sub CATMain()
	
	Dim ADoc as Document
	Set ADoc = CATIA.Documents.NewFrom ("C:\Users\gaochaofeng\Desktop\121.CATPart")

End Sub
