'Name:Recognizing Geometric Elements
'Version: 
'Code:CATIA CATScript
'Purpose: 识别几何元素
'Author:gaochaofeng  
'Date:31.3.2022
'Change:

Sub CATMain()
	
	Dim oPart as Part
	Dim oBody as Body
	Dim Geos as GeometricElements
	Dim Geo as GeometricElement
	
	Set oPart = CATIA.ActiveDocument.Part
	Set oBody = oPart.MainBody
	Set Geos = oBody.Sketches.Item("草图.1").GeometricElements
	If Geos.Count > 0 Then
		For I = 1 To Geos.Count
			Set Geo = Geos.Item(I)
			If Geo.GeometricType = catGeoTypeLine2D Then
				MsgBox (Geo.Name)
			End If
		Next
	End If
					
End Sub
