'Name:Subroutine
'Version: 
'Code:CATIA CATScript
'Purpose: 子程序示例
'Author:gaochaofeng  
'Date:26.03.2022
'Change:

Sub CATmain( )
	MultiplicationOutput 1 , 3
	MultiplicationOutput 2 , 3
	MultiplicationOutput 16 , 32
End Sub
Sub MultiplicationOutput (i , j as integer)
	Dim Box
	Box =MsgBox ( i * j )
End Sub
